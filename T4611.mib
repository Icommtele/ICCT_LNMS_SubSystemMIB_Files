-----------------------------------------------------------------------
-- MIB table for T4611
--
-- v1.0 for firmware 1-5-5.x, 2013-03-04
-----------------------------------------------------------------------
T4611-MIB DEFINITIONS ::= BEGIN


IMPORTS
	enterprises
		FROM RFC1155-SMI
	OBJECT-TYPE
		FROM RFC-1212;

  DisplayString ::= OCTET STRING


comet      OBJECT IDENTIFIER ::= { enterprises 22626 }
products   OBJECT IDENTIFIER ::= { comet 1 }
t4611      OBJECT IDENTIFIER ::= { products 2 }
values     OBJECT IDENTIFIER ::= { t4611 1 }
global     OBJECT IDENTIFIER ::= { t4611 2 }
valuesInt  OBJECT IDENTIFIER ::= { t4611 3 }
settings   OBJECT IDENTIFIER ::= { t4611 4 }
traps      OBJECT IDENTIFIER ::= { t4611 5 }
tables	   OBJECT IDENTIFIER ::= { t4611 6 }


-----------------------------------------------------------------------
-- Measured values - String
-----------------------------------------------------------------------
temp OBJECT-TYPE
	SYNTAX		DisplayString (SIZE (0..8))
	ACCESS		read-only
	STATUS		mandatory
	DESCRIPTION	"Temperature"
::= { values 1 }

tempAlarm OBJECT-TYPE
	SYNTAX		DisplayString (SIZE (0..8))
	ACCESS		read-only
	STATUS		mandatory
	DESCRIPTION	"Alarm on Temperature; none, high, low"
::= { values 5 }

tempUnit OBJECT-TYPE
	SYNTAX  	DisplayString (SIZE (0..8))
	ACCESS		read-only
	STATUS		mandatory
	DESCRIPTION	"Temperature Unit"
::= { values 9 }


-----------------------------------------------------------------------
-- Device informations
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- Measured values - Integer
-----------------------------------------------------------------------
tempInt OBJECT-TYPE
	SYNTAX		INTEGER (-5000..20000)
	ACCESS		read-only
	STATUS		mandatory
	DESCRIPTION	"Temperature (value*10)"
::= { valuesInt 1 }

tempAlarmInt OBJECT-TYPE
	SYNTAX		INTEGER (0..2)
	ACCESS		read-only
	STATUS		mandatory
	DESCRIPTION	"Alarm on Temperature; 0 - No, 1 - High, 2 - Low"
::= { valuesInt 5 }


-----------------------------------------------------------------------
-- Alarm settings
-----------------------------------------------------------------------
tempLowInt OBJECT-TYPE
	SYNTAX		INTEGER (-5000..20000)
	ACCESS		read-only
	STATUS		mandatory
	DESCRIPTION	"Temperature Limit Low (value*10)"
::= { settings 1 }

tempHighInt OBJECT-TYPE
	SYNTAX		INTEGER (-5000..20000)
	ACCESS		read-only
	STATUS		mandatory
	DESCRIPTION	"Temperature Limit High (value*10)"
::= { settings 2 }

tempDelayInt OBJECT-TYPE
	SYNTAX		INTEGER (0..4500)
	ACCESS		read-only
	STATUS		mandatory
	DESCRIPTION	"Temperature alaram delay [sec]"
::= { settings 7 }

tempHystInt OBJECT-TYPE
	SYNTAX		INTEGER (0..10000)
	ACCESS		read-only
	STATUS		mandatory
	DESCRIPTION	"Temperature hysteresis (value*10)"
::= { settings 10 }


-----------------------------------------------------------------------
-- traps
-----------------------------------------------------------------------
messageString OBJECT-TYPE
	SYNTAX		DisplayString (SIZE (0..32))
	ACCESS		read-only
	STATUS		mandatory
	DESCRIPTION	"Message giving more detailed information on alarms"
::= { traps 1 }


-----------------------------------------------------------------------
-- tables
-----------------------------------------------------------------------
historyTable OBJECT-TYPE
	SYNTAX		SEQUENCE OF HistoryEntry
	ACCESS		not-accessible
	STATUS		mandatory
	DESCRIPTION	"Table of the history values"
::= { tables 1 }

historyEntry OBJECT-TYPE
	SYNTAX		HistoryEntry
	ACCESS		not-accessible
	STATUS		optional
	DESCRIPTION	"History values entries"
	INDEX		{ histTemp }
::= { historyTable 1 }

HistoryEntry ::=
	SEQUENCE {
		histTemp
			INTEGER
		}

histTemp OBJECT-TYPE
	SYNTAX		INTEGER(-5000..20000)
	ACCESS		read-only
	STATUS		mandatory
	DESCRIPTION	"Temperature reading"
::= { historyEntry 1 }

END

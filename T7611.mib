-----------------------------------------------------------------------
-- MIB table for T7611
--
-- v1.0 for firmware 1-5-5.x, 2013-03-04
-----------------------------------------------------------------------
T7611-MIB DEFINITIONS ::= BEGIN


IMPORTS
	enterprises
		FROM RFC1155-SMI
	OBJECT-TYPE
		FROM RFC-1212;

  DisplayString ::= OCTET STRING


comet      OBJECT IDENTIFIER ::= { enterprises 22626 }
products   OBJECT IDENTIFIER ::= { comet 1 }
t7611      OBJECT IDENTIFIER ::= { products 2 }
values     OBJECT IDENTIFIER ::= { t7611 1 }
global     OBJECT IDENTIFIER ::= { t7611 2 }
valuesInt  OBJECT IDENTIFIER ::= { t7611 3 }
settings   OBJECT IDENTIFIER ::= { t7611 4 }
traps      OBJECT IDENTIFIER ::= { t7611 5 }
tables	   OBJECT IDENTIFIER ::= { t7611 6 }


-----------------------------------------------------------------------
-- Measured values - String
-----------------------------------------------------------------------
temp OBJECT-TYPE
	SYNTAX		DisplayString (SIZE (0..8))
	ACCESS		read-only
	STATUS		mandatory
	DESCRIPTION	"Temperature"
::= { values 1 }

hum OBJECT-TYPE
	SYNTAX		DisplayString (SIZE (0..8))
	ACCESS		read-only
	STATUS		mandatory
	DESCRIPTION	"Relative humidity"
::= { values 2 }

compVal OBJECT-TYPE
	SYNTAX		DisplayString (SIZE (0..8))
	ACCESS		read-only
	STATUS		mandatory
	DESCRIPTION	"Computed value"
::= { values 3 }

press OBJECT-TYPE
	SYNTAX		DisplayString (SIZE (0..8))
	ACCESS		read-only
	STATUS		mandatory
	DESCRIPTION	"Atmospheric pressure"
::= { values 4 }

tempAlarm OBJECT-TYPE
	SYNTAX		DisplayString (SIZE (0..8))
	ACCESS		read-only
	STATUS		mandatory
	DESCRIPTION	"Alarm on Temperature; none, high, low"
::= { values 5 }

humAlarm OBJECT-TYPE
	SYNTAX		DisplayString (SIZE (0..8))
	ACCESS		read-only
	STATUS		mandatory
	DESCRIPTION	"Alarm on Relative humidity; none, high, low"
::= { values 6 }

compValAlarm OBJECT-TYPE
	SYNTAX		DisplayString (SIZE (0..8))
	ACCESS		read-only
	STATUS		mandatory
	DESCRIPTION	"Alarm on Computed value; none, high, low"
::= { values 7 }

pressAlarm OBJECT-TYPE
	SYNTAX		DisplayString (SIZE (0..8))
	ACCESS		read-only
	STATUS		mandatory
	DESCRIPTION	"Alarm on Atmospheric pressure; none, high, low"
::= { values 8 }

tempUnit OBJECT-TYPE
	SYNTAX  	DisplayString (SIZE (0..8))
	ACCESS		read-only
	STATUS		mandatory
	DESCRIPTION	"Temperature Unit"
::= { values 9 }

humUnit OBJECT-TYPE
	SYNTAX  	DisplayString (SIZE (0..8))
	ACCESS		read-only
	STATUS		mandatory
	DESCRIPTION	"Relative humidity Unit"
::= { values 10 }

compValUnit OBJECT-TYPE
	SYNTAX  	DisplayString (SIZE (0..8))
	ACCESS		read-only
	STATUS		mandatory
	DESCRIPTION	"Computed value Unit"
::= { values 11 }

pressUnit OBJECT-TYPE
	SYNTAX  	DisplayString (SIZE (0..8))
	ACCESS		read-only
	STATUS		mandatory
	DESCRIPTION	"Atmospheric pressure Unit"
::= { values 12 }


-----------------------------------------------------------------------
-- Device informations
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- Measured values - Integer
-----------------------------------------------------------------------
tempInt OBJECT-TYPE
	SYNTAX		INTEGER (-5000..20000)
	ACCESS		read-only
	STATUS		mandatory
	DESCRIPTION	"Temperature (value*10)"
::= { valuesInt 1 }

humInt OBJECT-TYPE
	SYNTAX		INTEGER (-5000..20000)
	ACCESS		read-only
	STATUS		mandatory
	DESCRIPTION	"Relative humidity (value*10)"
::= { valuesInt 2 }

compValInt OBJECT-TYPE
	SYNTAX		INTEGER (-5000..20000)
	ACCESS		read-only
	STATUS		mandatory
	DESCRIPTION	"Computed value (value*10)"
::= { valuesInt 3 }

pressInt OBJECT-TYPE
	SYNTAX		INTEGER (-5000..20000)
	ACCESS		read-only
	STATUS		mandatory
	DESCRIPTION	"Atmospheric pressure (value*X)"
::= { valuesInt 4 }

tempAlarmInt OBJECT-TYPE
	SYNTAX		INTEGER (0..2)
	ACCESS		read-only
	STATUS		mandatory
	DESCRIPTION	"Alarm on Temperature; 0 - No, 1 - High, 2 - Low"
::= { valuesInt 5 }

humAlarmInt OBJECT-TYPE
	SYNTAX		INTEGER (0..2)
	ACCESS		read-only
	STATUS		mandatory
	DESCRIPTION	"Alarm on Relative humidity; 0 - No, 1 - High, 2 - Low"
::= { valuesInt 6 }

compValAlarmInt OBJECT-TYPE
	SYNTAX		INTEGER (0..2)
	ACCESS		read-only
	STATUS		mandatory
	DESCRIPTION	"Alarm on Computed value; 0 - No, 1 - High, 2 - Low"
::= { valuesInt 7 }

pressAlarmInt OBJECT-TYPE
	SYNTAX		INTEGER (0..2)
	ACCESS		read-only
	STATUS		mandatory
	DESCRIPTION	"Alarm on Atmospheric pressure; 0 - No, 1 - High, 2 - Low"
::= { valuesInt 8 }


-----------------------------------------------------------------------
-- Alarm settings
-----------------------------------------------------------------------
tempLowInt OBJECT-TYPE
	SYNTAX		INTEGER (-5000..20000)
	ACCESS		read-only
	STATUS		mandatory
	DESCRIPTION	"Temperature Limit Low (value*10)"
::= { settings 1 }

tempHighInt OBJECT-TYPE
	SYNTAX		INTEGER (-5000..20000)
	ACCESS		read-only
	STATUS		mandatory
	DESCRIPTION	"Temperature Limit High (value*10)"
::= { settings 2 }

humLowInt OBJECT-TYPE
	SYNTAX		INTEGER (-5000..20000)
	ACCESS		read-only
	STATUS		mandatory
	DESCRIPTION	"Humidity Limit Low (value*10)"
::= { settings 3 }

humHighInt OBJECT-TYPE
	SYNTAX		INTEGER (-5000..20000)
	ACCESS		read-only
	STATUS		mandatory
	DESCRIPTION	"Humidity Limit High (value*10)"
::= { settings 4 }

compValLowInt OBJECT-TYPE
	SYNTAX		INTEGER (-5000..20000)
	ACCESS		read-only
	STATUS		mandatory
	DESCRIPTION	"Computed value Limit Low (value*10)"
::= { settings 5 }

compValHighInt OBJECT-TYPE
	SYNTAX		INTEGER (-5000..20000)
	ACCESS		read-only
	STATUS		mandatory
	DESCRIPTION	"Computed value Limit High (value*10)"
::= { settings 6 }

tempDelayInt OBJECT-TYPE
	SYNTAX		INTEGER (0..4500)
	ACCESS		read-only
	STATUS		mandatory
	DESCRIPTION	"Temperature alaram delay [sec]"
::= { settings 7 }

humDelayInt OBJECT-TYPE
	SYNTAX		INTEGER (0..4500)
	ACCESS		read-only
	STATUS		mandatory
	DESCRIPTION	"Humidity alaram delay [sec]"
::= { settings 8 }

compValDelayInt OBJECT-TYPE
	SYNTAX		INTEGER (0..4500)
	ACCESS		read-only
	STATUS		mandatory
	DESCRIPTION	"Computed value alaram delay [sec]"
::= { settings 9 }

tempHystInt OBJECT-TYPE
	SYNTAX		INTEGER (0..10000)
	ACCESS		read-only
	STATUS		mandatory
	DESCRIPTION	"Temperature hysteresis (value*10)"
::= { settings 10 }

humHystInt OBJECT-TYPE
	SYNTAX		INTEGER (0..10000)
	ACCESS		read-only
	STATUS		mandatory
	DESCRIPTION	"Humidity hysteresis (value*10)"
::= { settings 11 }

compValHystInt OBJECT-TYPE
	SYNTAX		INTEGER (0..10000)
	ACCESS		read-only
	STATUS		mandatory
	DESCRIPTION	"Computed value hysteresis (value*10)"
::= { settings 12 }

pressLowInt OBJECT-TYPE
	SYNTAX		INTEGER (-5000..20000)
	ACCESS		read-only
	STATUS		mandatory
	DESCRIPTION	"Atmospheric pressure Limit Low (value*X)"
::= { settings 13 }

pressHighInt OBJECT-TYPE
	SYNTAX		INTEGER (-5000..20000)
	ACCESS		read-only
	STATUS		mandatory
	DESCRIPTION	"Atmospheric pressure Limit High (value*X)"
::= { settings 14 }

pressDelayInt OBJECT-TYPE
	SYNTAX		INTEGER (0..4500)
	ACCESS		read-only
	STATUS		mandatory
	DESCRIPTION	"Atmospheric pressure alaram delay [sec]"
::= { settings 15 }

pressHystInt OBJECT-TYPE
	SYNTAX		INTEGER (0..10000)
	ACCESS		read-only
	STATUS		mandatory
	DESCRIPTION	"Atmospheric pressure hysteresis (value*X)"
::= { settings 16 }


-----------------------------------------------------------------------
-- traps
-----------------------------------------------------------------------
messageString OBJECT-TYPE
	SYNTAX		DisplayString (SIZE (0..32))
	ACCESS		read-only
	STATUS		mandatory
	DESCRIPTION	"Message giving more detailed information on alarms"
::= { traps 1 }


-----------------------------------------------------------------------
-- tables
-----------------------------------------------------------------------
historyTable OBJECT-TYPE
	SYNTAX		SEQUENCE OF HistoryEntry
	ACCESS		not-accessible
	STATUS		mandatory
	DESCRIPTION	"Table of the history values"
::= { tables 1 }

historyEntry OBJECT-TYPE
	SYNTAX		HistoryEntry
	ACCESS		not-accessible
	STATUS		optional
	DESCRIPTION	"History values entries"
	INDEX		{ histTemp }
::= { historyTable 1 }

HistoryEntry ::=
	SEQUENCE {
		histTemp
			INTEGER,
		histHum
			INTEGER,
		histCompVal
			INTEGER,
		histPress
			INTEGER
		}

histTemp OBJECT-TYPE
	SYNTAX		INTEGER(-5000..20000)
	ACCESS		read-only
	STATUS		mandatory
	DESCRIPTION	"Temperature reading"
::= { historyEntry 1 }

histHum OBJECT-TYPE
	SYNTAX		INTEGER(-5000..20000)
	ACCESS		read-only
	STATUS		mandatory
	DESCRIPTION	"Humidity reading"
::= { historyEntry 2 }

histCompVal OBJECT-TYPE
	SYNTAX		INTEGER (-5000..20000)
	ACCESS		read-only
	STATUS		mandatory
	DESCRIPTION	"Computed value reading"
::= { historyEntry 3 }

histPress OBJECT-TYPE
	SYNTAX		INTEGER(-5000..20000)
	ACCESS		read-only
	STATUS		mandatory
	DESCRIPTION	"Atmospheric pressure reading"
::= { historyEntry 4 }

END
